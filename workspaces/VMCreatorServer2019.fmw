FME workspace VMCreatorServer2019.fmw
Title: Amazon EC2 Virtual Machine Creator
Description: This virtual machine contains FME Desktop 2019.0.1 and FME Server 2019.1 Beta.
Enter your full name and email address below and press 'Run'
You will be sent an email with instructions how to connect to your virtual machine.

Parameters:
- FullName = Ryan Cragg   # Enter your full name
- EmailAddress = ryan.cragg+1@safe.com   # Enter your email address and press 'Run'
- branch = Server2019   # " " GitHub Branch. Also AMI Description
- PublicIpAttempts = 60   # How many times should we try to get a PublicIpAddress?
- GMAIL_NAMED_CONNECTION = train@safe.com   # \"Google Gmail\" Gmail Connection

Note: Instance Exists
Junction
    -> Junction_2
Note: Instance Exists
Junction_2
    -> UUIDGenerator

Bookmark: Set Tags and other Parameters
Creator_Begin
    GEOMTYPE = Geometry Object
    NUM = 1
    CREATED -> AWSCredentialSupplier
Note: Get aws_access_key_id and aws_secret_access_key
AWSCredentialSupplier
    AWS_ACCESS_KEY_ID = AKIAICERN4WDSWP5VUDQ
    AWS_SECRET_ACCESS_KEY =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
    -> Tester_valid_email
Note: Set most tags and UserData
AttributeManager
    ATTR_TABLE:
      SET_TO git.username = $(git.username)
      SET_TO git.repository = $(git.repository)
      SET_TO git.branch = $(branch)
      SET_TO FullName = $(FullName)
      SET_TO EmailAddress = $(EmailAddress)
      SET_TO email = @ReplaceString($(EmailAddress)," ",+)
      SET_TO tag.created = @DateTimeNow()
      SET_TO tag.createdBy = @Value(git.branch) virtual machine generator
      SET_TO tag.purpose = Used for @Value(git.branch) by @Value(EmailAddress)
    -> FeatureReader [INITIATOR]
Note: Retrieve settings from settings.json
FeatureReader
    ATTRIBUTES = JSONFeature,"git.username,git.repository,git.branch,aws.name_tag,aws.s3_bucket_name,aws.region_name,aws.vpc_cidr,aws.subnet_cidr{},ami.linux,ami.windows,flexnet.ec2type,flexnet.ec2size,flexnet.volumeSize,flexnet.securityGroup,fmeserver.ec2type,fmeserver.ec2size,fmeserver.volumeSize,fmeserver.securityGroup,fmeserver.docker-compose.yaml,fmeserver.vm.repository,fmeserver.vm.workspace,fmeserver.vm.server,fmeserver.vm.token,fme.ec2type,fme.ec2size,fme.volumeSize,fme.securityGroup,fme.timezone,fme.portForwarding,fme.password,fme.installApps,fme.vm.instanceInitiatedShutdownBehavior,fme.vm.fromEmail,fme.vm.CCEmail,fme.vm.BCCEmail,web.repository,web.workspace,web.server,web.token,fme.vm.template.email{},fme.vm.template.rdp{},fme_geometry{0}"
    ATTR_ACCUM_MODE = Merge Initiator and Result
    ATTR_CONFLICT_RES = Use Result
    COMBINE_GEOM = Use Result
    DATASET = https://raw.githubusercontent.com/@Value(git.username)/@Value(git.repository)/@Value(git.branch)/settings.json
    FORMAT = JSON
    JSON_DECODE_TEXT_STRINGS = Yes
    JSON_FEATURE_TYPE_KEY = json_featuretype
    JSON_FLATTEN_MODE = ALL_LEVELS
    JSON_GEOMETRY_FORMAT = None
    JSON_SAVE_FRAGMENTS = NO
    JSON_SCAN_MODE = AUTO
    JSON_USE_BASENAME_AS_DEFAULT_FEATURE_TYPE = No
    JSON_USE_SEARCH_ENVELOPE = NO
    OUTPUT_FEATURES_DISPLAY = Schema and Data Features
    JSONFeature -> ListConcatenator_email_template

Bookmark: Check validity of published parameters
Note: Check that email is valid. Has @ in it.
Tester_valid_email
    BOOL_OP = OR
    TEST_CLAUSE = CASE_INSENSITIVE_TEST $(EmailAddress) CONTAINS @
    TEST_MODE = TEST
    PASSED -> AttributeManager
    FAILED -> Terminator
Terminator
    MESSAGE = Invalid email address

Bookmark: Clean up email and rdp templates
Note: The sad truth is that json doesn't support multi-line text. So each line has to be an element. So we have to concatenate it together here and in the next transformer
ListConcatenator_email_template
    DROP_EMPTY_PARTS = No
    LIST_ATTR = fme.vm.template.email{}
    SEP = "\n"
    VAL_ATTR = fme.vm.template.email
    -> ListConcatenator_rdp_template
ListConcatenator_rdp_template
    DROP_EMPTY_PARTS = No
    LIST_ATTR = fme.vm.template.rdp{}
    SEP = "\n"
    VAL_ATTR = fme.vm.template.rdp
    -> AttributeRemover
AttributeRemover
    LIST_ATTRS = fme.vm.template.email{} fme.vm.template.rdp{} fme_geometry{}
    REMOVE_ATTRS = flexnet.securityGroup,web.repository,flexnet.ec2size,fmeserver.vm.repository,fmeserver.securityGroup,web.token,fmeserver.volumeSize,flexnet.volumeSize,fmeserver.vm.token,web.server,ami.linux,fmeserver.vm.server,flexnet.ec2type,ami.windows,fmeserver.docker-compose.yaml,fmeserver.ec2size,fmeserver.ec2type,fmeserver.vm.workspace,web.workspace
    -> PythonCaller_Describe_vpc

Bookmark: Find VPC
Note: Find VPC via Name tag
PythonCaller_Describe_vpc
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.describe_vpcs(
                  Filters=[
                      {
                          'Name': 'tag:Name',
                          'Values': [
                              feature.getAttribute('aws.name_tag'),
                          ]
                      },
                  ],
              )
              feature.setAttribute("_response", json.dumps(response, default=str)) #https://stackoverflow.com/questions/11875770/how-to-overcome-datetime-datetime-not-json-serializable
          except Exception as e:
              feature.setAttribute("_exception", 'error in PythonCaller_run_instances: ' + repr(e))
    PYTHONSYMBOL = AWSCall
    -> JSONFlattener_vpcs
    -> Tester_has_exception
JSONFlattener_vpcs
    ERROR_LIST_ATTR = _json_error
    JSON_DOCUMENT = @Value(_response)
    READ_FROM_FILE = NO
    RECURSIVE = Yes
    -> AttributeRenamer_VpcId
AttributeRenamer_VpcId
    ATTR_TABLE = RENAME_SET_DEFAULT Vpcs{0}.VpcId > VpcId
    -> PythonCaller_Describe_subnet

Bookmark: Find Subnet
Note: Get list of subnets
PythonCaller_Describe_subnet
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.describe_subnets(
                  Filters=[
                      {
                          'Name': 'vpc-id',
                          'Values': [
                              feature.getAttribute('VpcId'),
                          ]
                      },
                  ],
              )
              feature.setAttribute("_response", json.dumps(response, default=str)) #https://stackoverflow.com/questions/11875770/how-to-overcome-datetime-datetime-not-json-serializable
          except Exception as e:
              feature.setAttribute("_exception", 'error in PythonCaller: ' + repr(e))
    PYTHONSYMBOL = AWSCall
    -> JSONFlattener_subnet
    -> Tester_has_exception
JSONFlattener_subnet
    ERROR_LIST_ATTR = _json_error
    JSON_DOCUMENT = @Value(_response)
    NEW_ATTRIBUTES = Subnets{} State SubnetId
    READ_FROM_FILE = NO
    RECURSIVE = Yes
    -> ListExploder_2
ListExploder_2
    ATTR_ACCUM_MODE = Merge List Attributes
    ATTR_CONFLICT_RES = Use List Attribute Values
    INDEX_ATTR = _element_index
    LIST_ATTR = Subnets{}
    ELEMENTS -> Tester_subnet_available
Note: Find an available subnet
Tester_subnet_available
    BOOL_OP = OR
    TEST_CLAUSE = TEST @Value(State) = available
    TEST_MODE = TEST
    PASSED -> Sampler_subnet
Note: We only need one. Get a random subnet in case the first one is full
Sampler_subnet
    RATE = 1
    SAMPLE_MODE = Yes
    SAMPLE_TYPE_LONG = First N Features
    SAMPLED -> PythonCaller_Describe_security_groups

Bookmark: Find Security Group
Note: Find the security groups
PythonCaller_Describe_security_groups
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.describe_security_groups(
                  Filters=[
                      {
                          'Name': 'vpc-id',
                          'Values': [
                              feature.getAttribute('VpcId'),
                          ]
                      },
                      {
                          'Name': 'group-name',
                          'Values': [
                              feature.getAttribute('fme.securityGroup'),
                          ]
                      },
                  ],

              )
              feature.setAttribute("_response", json.dumps(response, default=str)) #https://stackoverflow.com/questions/11875770/how-to-overcome-datetime-datetime-not-json-serializable
          except Exception as e:
              feature.setAttribute("_exception", 'error in PythonCaller_run_instances: ' + repr(e))
    PYTHONSYMBOL = AWSCall
    -> JSONFlattener_security
    -> Tester_has_exception
JSONFlattener_security
    ERROR_LIST_ATTR = _json_error
    JSON_DOCUMENT = @Value(_response)
    NEW_ATTRIBUTES = SecurityGroups{}.GroupId GroupId GroupName
    READ_FROM_FILE = NO
    RECURSIVE = Yes
    -> AttributeManager_more_tags_and_stuff
AttributeManager_more_tags_and_stuff
    ATTR_TABLE:
      SET_TO tag.team = Train
      SET_TO tag.owner = @Value(fme.vm.fromEmail)
      SET_TO GroupId = @Value(SecurityGroups{0}.GroupId)
    -> PythonCaller_DescribeInstances

Bookmark: Does Instance Exist?
Note: Will have to test if the machine doesn't exist.
PythonCaller_DescribeInstances
    NEW_ATTRIBUTES = _response
    PYTHONSOURCE:
      import fme
      import fmeobjects
      import boto3    #need this for AWS access
      import json     #AWS stuff creates json


      def AWSCall(feature):
          ec2 = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = ec2.describe_instances(
                  Filters=[
                      {
                          'Name': 'tag:Purpose',
                          'Values': [
                              feature.getAttribute('tag.purpose'),
                          ]
                      },
                  ],
              )
              feature.setAttribute("_response", json.dumps(response, default=str)) #https://stackoverflow.com/questions/11875770/how-to-overcome-datetime-datetime-not-json-serializable
          except:
              feature.setAttribute("_response", 'Error in PythonCaller_DescribeInstances')
    PYTHONSYMBOL = AWSCall
    -> JSONFlattener_DescribeInstances
JSONFlattener_DescribeInstances
    ERROR_LIST_ATTR = _json_error
    JSON_DOCUMENT = @Value(_response)
    NEW_ATTRIBUTES = Reservations{}
    RECURSIVE = Yes
    -> ListExploder_Reservations
Note: If it can't explode Reservations, that means the instance does not exist. Rejected has the feature for creating an instance.But we still have to test for Terminated vs Stopped vs Pending vs Shutting Down
ListExploder_Reservations
    ATTR_ACCUM_MODE = Merge List Attributes
    ATTR_CONFLICT_RES = Use List Attribute Values
    INDEX_ATTR = _element_index
    LIST_ATTR = Reservations{}
    ELEMENTS -> AttributeExposer_Instances_list
    <REJECTED> -> Junction_3
AttributeExposer_Instances_list
    ATTR_LIST = Instances{}
    -> ListExploder_Instances
ListExploder_Instances
    ATTR_ACCUM_MODE = Merge List Attributes
    ATTR_CONFLICT_RES = Use List Attribute Values
    INDEX_ATTR = _element_index
    LIST_ATTR = Instances{}
    ELEMENTS -> AttributeExposer_PublicIpAddress
AttributeExposer_PublicIpAddress
    ATTR_LIST = State.Name,PublicIpAddress
    -> AttributeFilter
Note: At this point, there can be instances in many different states. We only care about running and pending
AttributeFilter
    ATTR_NAME = State.Name
    ATTR_VALUES = <Empty>,<Missing>,<Null>,<Unfiltered>,running,pending
    <EMPTY> -> FeatureHolder
    <MISSING> -> FeatureHolder
    <NULL> -> FeatureHolder
    <UNFILTERED> -> FeatureHolder
    running -> Sampler
    pending -> Sampler
Note: Hold back the instances that are not in the running or pending states
FeatureHolder
    -> Sampler
Note: If anything is running or pending, it will get here first, and be sampled first.
Sampler
    RATE = 1
    SAMPLE_MODE = No
    SAMPLE_TYPE_LONG = First N Features
    SAMPLED -> AttributeFilter_state
Note: Check instance state
AttributeFilter_state
    ATTR_NAME = State.Name
    ATTR_VALUES = <Empty>,<Missing>,<Null>,<Unfiltered>,running,pending
    <EMPTY> -> Junction_3
    <MISSING> -> Junction_3
    <NULL> -> Junction_3
    <UNFILTERED> -> Junction_3
    running -> Junction
    pending -> Junction
Note: Instance does not exist
Junction_3
    -> PythonCaller_describe_images

Bookmark: Find ImageId
PythonCaller_describe_images
    NEW_ATTRIBUTES = _response CreationDate
    PYTHONSOURCE:
      import fme
      import fmeobjects
      import boto3    #need this for AWS access
      import json     #AWS stuff creates json

      def AWSCall(feature):
          ec2 = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = ec2.describe_images(
                  Owners=[
                      'self',
                  ],
                  Filters=[
                      {
                          'Name': 'description',
                                  'Values': [
                                  '*'+feature.getAttribute('git.branch')+'*',
                          ]
                      },
                  ],
              )
              feature.setAttribute("_response", json.dumps(response))
          except:
              feature.setAttribute("_exception", 'Error in PythonCaller_describe_images')
    PYTHONSYMBOL = AWSCall
    -> JSONFlattener_describe_images
    -> Tester_has_exception
Note: Images{}
JSONFlattener_describe_images
    ERROR_LIST_ATTR = _json_error
    JSON_DOCUMENT = @Value(_response)
    NEW_ATTRIBUTES = Images{}
    RECURSIVE = Yes
    -> ListExploder
ListExploder
    ATTR_ACCUM_MODE = Merge List Attributes
    ATTR_CONFLICT_RES = Use List Attribute Values
    INDEX_ATTR = _element_index
    LIST_ATTR = Images{}
    ELEMENTS -> Sorter_by_CreationDate
Sorter_by_CreationDate
    SORT_PARM = CreationDate ALPHA DESCENDING
    SORTED -> Tester_image_state_available
Tester_image_state_available
    BOOL_OP = OR
    COMPOSITE_TEST = 1
    TEST_CLAUSE = TEST @Value(State) = available
    TEST_MODE = TEST
    PASSED -> AttributeRenamer_ImageId
AttributeRenamer_ImageId
    ATTR_TABLE = RENAME_SET_DEFAULT Images{0}.ImageId > ImageId
    -> TesterImageId
TesterImageId
    BOOL_OP = OR
    TEST_CLAUSE = TEST ImageId ATTRIBUTE_HAS_A_VALUE ""
    TEST_MODE = TEST
    PASSED -> PythonCaller_run_instances
    FAILED -> Terminator_ImageId
Terminator_ImageId
    MESSAGE = ImageID not found

Bookmark: Create Instance
Note: This creates the ec2 instance. But it takes a while for the Public IP address to be assigned, so we grab the Public Ip address later
PythonCaller_run_instances
    NEW_ATTRIBUTES = _response _exception
    PYTHONSOURCE:
      import fme
      import fmeobjects
      import boto3    #need this for AWS access
      import json     #AWS stuff creates json


      def AWSCall(feature):
          ec2 = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = ec2.run_instances(
                  ImageId= feature.getAttribute('ImageId'),
                  InstanceType= feature.getAttribute('fme.ec2type') + '.' + feature.getAttribute('fme.ec2size'),
                  SubnetId= feature.getAttribute('SubnetId'),
                  MinCount= 1, MaxCount= 1,
                  SecurityGroupIds=[
                          feature.getAttribute('GroupId'),
                      ],
                  InstanceInitiatedShutdownBehavior= feature.getAttribute('fme.vm.instanceInitiatedShutdownBehavior'),
                  TagSpecifications=[
                      {
                          'ResourceType': 'instance',
                          'Tags': [
                                          {'Key': 'Name', 'Value': feature.getAttribute('FullName')},
                                          {'Key': 'Created', 'Value': feature.getAttribute('tag.created')},
                                          {'Key': 'Created By', 'Value': feature.getAttribute('tag.createdBy')},
                                          {'Key': 'Team', 'Value': feature.getAttribute('tag.team')},
                                          {'Key': 'Owner', 'Value': feature.getAttribute('tag.owner')},
                                          {'Key': 'Purpose', 'Value': feature.getAttribute('tag.purpose')},
                                          {'Key': 'Email', 'Value': feature.getAttribute('email')},
                                   ]
                       },
                   ],

              )
              feature.setAttribute("_response", json.dumps(response, default=str)) #https://stackoverflow.com/questions/11875770/how-to-overcome-datetime-datetime-not-json-serializable
          except Exception as e:
              feature.setAttribute("_exception", 'error in PythonCaller_run_instances: ' + repr(e))
    PYTHONSYMBOL = AWSCall
    -> JSONFlattener_Run_instances
    -> Tester_has_exception
Note: Instances{0}.InstanceId
JSONFlattener_Run_instances
    ERROR_LIST_ATTR = _json_error
    JSON_DOCUMENT = @Value(_response)
    NEW_ATTRIBUTES = Instances{0}.InstanceId
    RECURSIVE = Yes
    -> AttributeRenamer
    <REJECTED> -> Terminator_run_instances
AttributeRenamer
    ATTR_TABLE = RENAME_SET_DEFAULT Instances{0}.InstanceId > InstanceId
    -> TesterInstanceId
Note: Sometimes the InstanceId doesnt' get populated. No idea why. Problem on Amazon's side.
TesterInstanceId
    BOOL_OP = OR
    TEST_CLAUSE = TEST InstanceId ATTRIBUTE_HAS_A_VALUE ""
    TEST_MODE = TEST
    PASSED -> Cloner_PublicIpAddress
    FAILED -> Terminator_InstanceId
Terminator_InstanceId
    MESSAGE = InstanceId failed to populate. @Value(_response)
Terminator_run_instances
    MESSAGE = @Value(_response)

Bookmark: Get ready for multiple tries at getting PublicIpAddress
Cloner_PublicIpAddress
    COPIES = $(PublicIpAttempts)
    COPYATT = _attempt
    COPY -> Sampler_First_IP_attempt
Note: Send a feature to retrieve PublicIpAddress. Have some backup features ready if it PublicIpAddress isn't available yet
Sampler_First_IP_attempt
    RATE = 1
    SAMPLE_MODE = No
    SAMPLE_TYPE_LONG = First N Features
    SAMPLED -> PythonCaller_DescribeInstances_PublicIpAddress
    NOT_SAMPLED -> VariableRetriever

Bookmark: PublicIpAddress not found. Try again
Note: Check to see if PublicIpAddress has been retrieved
VariableRetriever
    SCOPE = Global
    VALUE_ATTR = PublicIpAddress
    VARNAME = aVariable
    -> TestFilter
Note: First, check that we haven't run out of attempts. / Second, check that PublicIpAddress has no value. / Third, discard extra features if we do have PublicIpAddress
TestFilter
    DEFAULT_VALUE = <UNFILTERED>
    TEST_LIST:
      "BOOL_OP,AND,COMPOSITE_TEST,""""""<Unused>"""""",TEST_CLAUSE,TEST @Value(_attempt) = @Evaluate($(PublicIpAttempts)-1)
      TEST PublicIpAddress NOT_ATTRIBUTE_HAS_A_VALUE """,Error,"BOOL_OP,OR,COMPOSITE_TEST,""""""<Unused>"""""",TEST_CLAUSE,TEST PublicIpAddress NOT_ATTRIBUTE_HAS_A_VALUE """,No PublicIpAddress Yet
    Error -> Terminator_NoPublicIpAddress
    No PublicIpAddress Yet -> Decelerator
Terminator_NoPublicIpAddress
    MESSAGE = Translation Terminated. Something went wrong. Cannot obtain PublicIpAddress. Tried @Value(_attempt) times
Note: If we don't have PublicIpAddress yet, wait a beat and try again
Decelerator
    DECEL_TYPE = Per Feature Delay
    DELAY = 1
    -> PythonCaller_DescribeInstances_PublicIpAddress

Bookmark: Get PublicIpAddress of new instance
Note: Try to get the PublicIpAddress. It might not be ready yet
PythonCaller_DescribeInstances_PublicIpAddress
    NEW_ATTRIBUTES = _response
    PYTHONSOURCE:
      import fme
      import fmeobjects
      import boto3    #need this for AWS access
      import json     #AWS stuff creates json


      def AWSCall(feature):
          ec2 = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = ec2.describe_instances(
                  InstanceIds=[
                      feature.getAttribute('InstanceId'),
                      ]
              )
              feature.setAttribute("_response", json.dumps(response, default=str)) #https://stackoverflow.com/questions/11875770/how-to-overcome-datetime-datetime-not-json-serializable
          except Exception as e:
              feature.setAttribute("_exception", 'error in PythonCaller_DescribeInstances_PublicIpAddress: ' + repr(e))
    PYTHONSYMBOL = AWSCall
    -> JSONFlattener_response
    -> Tester_has_exception

Bookmark: Clean up PublicIpAddress response
Note: Reservations{0}.Instances{0}.PublicIpAddress
JSONFlattener_response
    ERROR_LIST_ATTR = _json_error
    JSON_DOCUMENT = @Value(_response)
    NEW_ATTRIBUTES = Reservations{0}.Instances{0}.State.Name Reservations{0}.Instances{0}.PublicIpAddress
    RECURSIVE = Yes
    -> AttributeRenamer_PublicIpAddress
    <REJECTED> -> AttributeRenamer_PublicIpAddress
AttributeRenamer_PublicIpAddress
    ATTR_TABLE = RENAME_SET_DEFAULT Reservations{0}.Instances{0}.PublicIpAddress > PublicIpAddress
    -> Tester_has_PublicIpAddress

Bookmark: Check for PublicIpAddress
Note: If we have PublicIpAddress, set the global variable so the other features don't make an attempt
Tester_has_PublicIpAddress
    BOOL_OP = OR
    TEST_CLAUSE = TEST PublicIpAddress ATTRIBUTE_HAS_A_VALUE ""
    TEST_MODE = TEST
    PASSED -> VariableSetter
VariableSetter
    SCOPE = Global
    VALUE = @Value(PublicIpAddress)
    VARNAME = aVariable
    -> Junction_2

Bookmark: Error in PythonCaller
Tester_has_exception
    BOOL_OP = OR
    TEST_CLAUSE = TEST _exception ATTRIBUTE_HAS_A_VALUE ""
    TEST_MODE = TEST
    PASSED -> Terminator_exception
Terminator_exception
    MESSAGE = Translation Terminated. @Value(_exception)

Bookmark: Create RDP File package
Note: unique value for temp folder
UUIDGenerator
    UUID_ATTR = _uuid
    -> Cloner
Note: I need a feature for each RDP file, / so I create 3 features here.
Cloner
    COPIES = 3
    COPYATT = _creation_instance
    COPY -> AttributeCreator_Port_FileName
Note: set the port numbers and output file names
AttributeCreator_Port_FileName
    ATTR_LIST = FolderName,$(FME_SHAREDRESOURCE_TEMP)Training/@Value(_uuid)/,FileName,"FME_CONDITIONAL:DEFAULT_VALUE'_FME_NO_OP_'BOOL_OP;OR;COMPOSITE_TEST;<Unused>;TEST @Value(_creation_instance) = 0'@Value(PublicIpAddress).rdp'BOOL_OP;OR;COMPOSITE_TEST;<Unused>;TEST @Value(_creation_instance) = 1'@Value(PublicIpAddress)Port8080.rdp'BOOL_OP;OR;COMPOSITE_TEST;<Unused>;TEST @Value(_creation_instance) = 2'@Value(PublicIpAddress)Port443.rdp'FME_NUM_CONDITIONS4___",PORT,"FME_CONDITIONAL:DEFAULT_VALUE'_FME_NO_OP_'BOOL_OP;OR;COMPOSITE_TEST;<Unused>;TEST @Value(_creation_instance) = 0'3389'BOOL_OP;OR;COMPOSITE_TEST;<Unused>;TEST @Value(_creation_instance) = 1'8080'BOOL_OP;OR;COMPOSITE_TEST;<Unused>;TEST @Value(_creation_instance) = 2'443'FME_NUM_CONDITIONS4___"
    -> AttributeCreatorRDP
Note: set the contents of the RDP file / Some useful info here: / http://chall32.blogspot.ca/2012/04/fixing-remote-desktop-annoyances.html
AttributeCreatorRDP
    ATTR_LIST:
      text_line_data,full address:s:@Value(PublicIpAddress):@Value(PORT)
      @Value(fme.vm.template.rdp)
    -> FeatureWriter [text_line]
FeatureWriter
    DATASET = @Value(FolderName)@Value(FileName)
    DATASET_ATTR = _dataset
    FEATURE_TYPE_LIST_ATTR = _feature_type
    FORMAT = TEXTLINE
    MORE_SUMMARY_ATTRS = FileName FolderName FullName PublicIpAddress _attempt email fme.ec2size fme.ec2type fme.installApps fme.password fme.portForwarding fme.securityGroup fme.timezone fme.vm.BCCEmail fme.vm.CCEmail fme.vm.fromEmail fme.vm.instanceInitiatedShutdownBehavior fme.vm.template.email fme.vm.template.rdp fme.volumeSize git.branch
    TEXTLINE_COORDINATE_SYSTEM_GRANULARITY = FEATURE
    TEXTLINE_DESTINATION_DATASETTYPE_VALIDATION = Yes
    TEXTLINE_ENCODING = SYSTEM
    TEXTLINE_END_OF_LINE = System
    TEXTLINE_MIME_TYPE = application/octet-stream
    TEXTLINE_OVERWRITE_FILE = NO
    TEXTLINE_WRITE_LAST_EOL = YES
    TEXTLINE_WRITE_UTF8_BOM = YES
    TOTAL_FEATURES_WRITTEN_ATTR = _total_features_written
    SUMMARY -> ListExploder_Summary
ListExploder_Summary
    ATTR_ACCUM_MODE = Merge List Attributes
    ATTR_CONFLICT_RES = Use List Attribute Values
    INDEX_ATTR = _element_index
    LIST_ATTR = _feature_type{}
    ELEMENTS -> Aggregator
Note: Sending 3 emails would be bad. Let's only send one.
Aggregator
    ACCUM_ATTRS_NAME = Use Attributes From One Feature
    AGGREGATE_TYPE = Homogeneous Collection (If Possible)
    GROUP_BY = fme.vm.fromEmail FullName fme.securityGroup fme.password fme.timezone fme.vm.CCEmail PublicIpAddress fme.installApps fme.vm.BCCEmail email fme.vm.template.email fme.ec2type fme.vm.instanceInitiatedShutdownBehavior fme.volumeSize fme.portForwarding fme.ec2size fme.vm.template.rdp
    LIST_NAME = _files
    MODE = Geometry - Assemble One Level
    ORDERED = No
    SEP = ,
    AGGREGATE -> StringReplacer_FullName
Note: The template doesn't work if it has @Value in it, so we replace the FullName with the attribute value here. / We can't do this earlier because we need the public ip address
StringReplacer_FullName
    CASE = NO
    FIND_TEXT = _FullName_
    NO_MATCH = _FME_NO_OP_
    REGEXP = NO
    REPLACE_TEXT = @Value(FullName)
    SRC_ATTRS = fme.vm.template.email
    -> StringReplacer_PublicIpAddress
Note: The template doesn't work if it has @Value in it, so we replace the PublicIpAddress with the attribute value here
StringReplacer_PublicIpAddress
    CASE = NO
    FIND_TEXT = _PublicIpAddress_
    NO_MATCH = _FME_NO_OP_
    REGEXP = NO
    REPLACE_TEXT = @Value(PublicIpAddress)
    SRC_ATTRS = fme.vm.template.email
    -> StringReplacer_password
StringReplacer_password
    CASE = NO
    FIND_TEXT = _fme.password_
    NO_MATCH = _FME_NO_OP_
    REGEXP = NO
    REPLACE_TEXT = @Value(fme.password)
    SRC_ATTRS = fme.vm.template.email
    -> Emailer
Emailer
    ATTACHMENTTABLE = @Value(_files{0}._dataset)  autodetect @Value(_files{1}._dataset)  autodetect @Value(_files{2}._dataset)  autodetect
    BCC = @Value(fme.vm.BCCEmail)
    BODY = @Value(fme.vm.template.email)
    FROM = @Value(fme.vm.fromEmail)
    SERVICE = Gmail
    SMTP_CONNECTION = GMAIL_NAMED_CONNECTION;$(GMAIL_NAMED_CONNECTION);TIMEOUT;60;FME_CONTROLLER_QUERY_FILE;transformers/dependencies/emailer/Gmail.fme
    SUBJECT = Your @TitleCase(@Value(git.branch)) Virtual Machine connection files
    TO = @Value(email)
    Sent -> AttributeKeeper
AttributeKeeper
    KEEP_ATTRS = CourseType,FullName,PublicIpAddress,email,FileName,FolderName,_attempt,name
    -> Emailer_Sent
Emailer_Sent: Logger
    LOG_FEATURE = LOG_ONLY
    MAXCOORDS = 20
    MAXFEATS = 20
    MESSAGE = EMAIL OUTPUT
    SEVERITY = INFO
