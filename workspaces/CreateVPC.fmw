FME workspace CreateVPC.fmw

Parameters:
- aws_connection = FME Virtual Machines IAM Amazon Web Services   # "Amazon Web Services" AWS Web Connection

Bookmark: Get parameters
Note: We need the aws access key and aws secret access key from the web connection for use in later PythonCallers.
PythonCreator_AWS_Credentials
    NEW_ATTRIBUTES = AWS_ACCESS_KEY AWS_SECRET_ACCESS_KEY
    PYTHONSOURCE_NEW:
      import fme
      import fmeobjects
      import collections

      from fmewebservices import FMETokenConnection  # noqa
      from fmegeneral.webservices import NamedConnectionManager

      def aws_credentials_from_conn_name(feature):
         # noinspection PyArgumentList
         named_connection = NamedConnectionManager().getNamedConnection(
             FME_MacroValues['aws_connection']
         )  # type: FMETokenConnection

         try:
             key_vals = named_connection.getKeyValues()
             key = key_vals.get("AWS_ACCESS_KEY", None)
             secret = key_vals.get("AWS_SECRET", None)
             feature.setAttribute("AWS_ACCESS_KEY", key)
             feature.setAttribute("AWS_SECRET_ACCESS_KEY", secret)
         except Exception as e:
             feature.setAttribute("_exception", 'PythonCreator_AWS_Credentials: ' + repr(e))
    PYTHONSYMBOL = aws_credentials_from_conn_name
    -> FeatureReader [INITIATOR]
Note: Get parameters from settings.json
FeatureReader
    ATTRIBUTES = JSONFeature,"git.username,git.repository,git.branch,aws.name_tag,aws.s3_bucket_name,aws.region_name,aws.vpc_cidr,aws.subnet_cidr{},ami.linux,ami.windows,flexnet.ec2type,flexnet.ec2size,flexnet.volumeSize,flexnet.securityGroup,fmeserver.ec2type,fmeserver.ec2size,fmeserver.volumeSize,fmeserver.securityGroup,fmeserver.docker-compose.yaml,fmeserver.vm.repository,fmeserver.vm.workspace,fmeserver.vm.server,fmeserver.vm.token,fme.ec2type,fme.ec2size,fme.volumeSize,fme.securityGroup,fme.timezone,fme.portForarding,fme.password,fme.installApps,fme.vm.instanceInitiatedShutdownBehavior,fme.vm.fromEmail,fme.vm.CCEmail,fme.vm.BCCEmail,web.repository,web.workspace,web.server,web.token,fme.vm.template.email{},fme.vm.template.rdp{},fme_geometry{0}"
    ATTR_ACCUM_MODE = Merge Initiator and Result
    ATTR_CONFLICT_RES = Use Result
    COMBINE_GEOM = Use Result
    DATASET = ../settings.json
    FORMAT = JSON
    JSON_DECODE_TEXT_STRINGS = Yes
    JSON_FEATURE_TYPE_KEY = json_featuretype
    JSON_FLATTEN_MODE = ALL_LEVELS
    JSON_GEOMETRY_FORMAT = None
    JSON_SAVE_FRAGMENTS = NO
    JSON_SCAN_MODE = AUTO
    JSON_USE_BASENAME_AS_DEFAULT_FEATURE_TYPE = No
    JSON_USE_SEARCH_ENVELOPE = NO
    OUTPUT_FEATURES_DISPLAY = Schema and Data Features
    JSONFeature -> AttributeRemover
Note: clean out what we don't need
AttributeRemover
    LIST_ATTRS = fme.vm.template.email{} fme.vm.template.rdp{}
    REMOVE_ATTRS = fmeserver.vm.server,ami.windows,fme.volumeSize,fmeserver.ec2type,fme.portForarding,fmeserver.vm.token,fme.vm.template.rdp{0},fmeserver.volumeSize,flexnet.volumeSize,web.token,fme.vm.BCCEmail,web.workspace,fmeserver.ec2size,fmeserver.docker-compose.yaml,fmeserver.vm.repository,fme.password,fme.vm.fromEmail,fme.ec2type,fme.vm.CCEmail,fme.timezone,web.repository,fme.installApps,flexnet.ec2type,fme_geometry{0},fme.ec2size,fme.vm.instanceInitiatedShutdownBehavior,fmeserver.vm.workspace,fme.vm.template.email{0},flexnet.ec2size,web.server,ami.linux
    -> PythonCaller_create_VPC

Bookmark: Create VPC
Note: Create VPC
PythonCaller_create_VPC
    NEW_ATTRIBUTES = _response
    PYTHONSOURCE:
      import fme
      import fmeobjects
      import boto3    #need this for AWS access
      import json     #AWS stuff creates json


      def AWSCall(feature):
          ec2 = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = ec2.create_vpc(
                  CidrBlock=feature.getAttribute('aws.vpc_cidr'),
              )
              feature.setAttribute("_response", json.dumps(response, default=str)) #https://stackoverflow.com/questions/11875770/how-to-overcome-datetime-datetime-not-json-serializable
          except Exception as e:
              feature.setAttribute("_exception", 'PythonCaller_create_VPC: ' + repr(e))
    PYTHONSYMBOL = AWSCall
    -> JSONFlattener_vpc
    -> AttributeExposer
JSONFlattener_vpc
    ERROR_LIST_ATTR = _json_error
    JSON_DOCUMENT = @Value(_response)
    NEW_ATTRIBUTES = Vpc.VpcId
    READ_FROM_FILE = NO
    RECURSIVE = Yes
    -> PythonCaller_create_vpc_tags
Note: Tag VPC
PythonCaller_create_vpc_tags
    NEW_ATTRIBUTES = _response
    PYTHONSOURCE:
      import fme
      import fmeobjects
      import boto3    #need this for AWS access
      import json     #AWS stuff creates json


      def AWSCall(feature):
          ec2 = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = ec2.create_tags(
                  Resources=[
                      feature.getAttribute('Vpc.VpcId'),
                  ],
                  Tags=[
                      {
                      'Key': 'Name',
                      'Value': feature.getAttribute('aws.name_tag')
                      },
                  ]
              )
              feature.setAttribute("_response", json.dumps(response, default=str)) #https://stackoverflow.com/questions/11875770/how-to-overcome-datetime-datetime-not-json-serializable
          except Exception as e:
              feature.setAttribute("_exception", 'PythonCaller_create_vpc_tags: ' + repr(e))
    PYTHONSYMBOL = AWSCall
    -> PythonCaller_create_fmeserver_security_group
    -> PythonCaller_create_fme_security_group
    -> PythonCaller_create_FlexNet_security_group
    -> PythonCaller_create_internet_gateway
    -> AttributeExposer
    -> Junction

Bookmark: Create FlexNet security group
PythonCaller_create_FlexNet_security_group
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.create_security_group(
                  Description='FME License Server',
                  GroupName=feature.getAttribute('flexnet.securityGroup'),
                  VpcId=feature.getAttribute('Vpc.VpcId'),
              )
              feature.setAttribute("_response", json.dumps(response, default=str)) #https://stackoverflow.com/questions/11875770/how-to-overcome-datetime-datetime-not-json-serializable
          except Exception as e:
              feature.setAttribute("_exception", 'error in PythonCaller_create_FlexNet_security_group: ' + repr(e))
    PYTHONSYMBOL = AWSCall
    -> JSONFlattener_flexnet
    -> AttributeExposer
JSONFlattener_flexnet
    ERROR_LIST_ATTR = _json_error
    JSON_DOCUMENT = @Value(_response)
    NEW_ATTRIBUTES = GroupId
    READ_FROM_FILE = NO
    RECURSIVE = Yes
    -> PythonCaller_modify_FlexNet
PythonCaller_modify_FlexNet
    NEW_ATTRIBUTES = _response
    PYTHONSOURCE:
      import fme
      import fmeobjects
      import boto3    #need this for AWS access
      import json     #AWS stuff creates json


      def AWSCall(feature):
          ec2 = boto3.resource(
                  'ec2',
                  region_name=feature.getAttribute('aws.region_name'),
                  aws_access_key_id=feature.getAttribute('AWS_ACCESS_KEY_ID'),
                  aws_secret_access_key=feature.getAttribute('AWS_SECRET_ACCESS_KEY'))
          security_group = ec2.SecurityGroup(feature.getAttribute('GroupId'))
          try:
              response = security_group.authorize_ingress(

                  IpPermissions=[
                      {
                          'FromPort': 80,
                          'IpProtocol': 'tcp',
                          'IpRanges': [
                              {
                                  'CidrIp': '0.0.0.0/0',
                              },
                          ],
                          'ToPort': 80,
                      },
                      {
                          'FromPort': 27000,
                          'IpProtocol': 'tcp',
                          'IpRanges': [
                              {
                                  'CidrIp': feature.getAttribute('aws.vpc_cidr'),
                              },
                          ],
                          'ToPort': 27010,
                      },
                  ],
              )
              feature.setAttribute("_response", json.dumps(response, default=str)) #https://stackoverflow.com/questions/11875770/how-to-overcome-datetime-datetime-not-json-serializable
          except Exception as e:
              feature.setAttribute("_exception", 'Error in PythonCaller_modify_FlexNet ' + repr(e))
    PYTHONSYMBOL = AWSCall
    -> AttributeExposer

Bookmark: Create FME Virtual Machine security group
PythonCaller_create_fme_security_group
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.create_security_group(
                  Description='FME Virtual Machines',
                  GroupName=feature.getAttribute('fme.securityGroup'),
                  VpcId=feature.getAttribute('Vpc.VpcId'),
              )
              feature.setAttribute("_response", json.dumps(response, default=str)) #https://stackoverflow.com/questions/11875770/how-to-overcome-datetime-datetime-not-json-serializable
          except Exception as e:
              feature.setAttribute("_exception", 'error in PythonCaller_create_fme_security_group: ' + repr(e))
    PYTHONSYMBOL = AWSCall
    -> JSONFlattener_flexnet_2
    -> AttributeExposer
JSONFlattener_flexnet_2
    ERROR_LIST_ATTR = _json_error
    JSON_DOCUMENT = @Value(_response)
    NEW_ATTRIBUTES = GroupId
    READ_FROM_FILE = NO
    RECURSIVE = Yes
    -> PythonCaller_modify_fme
PythonCaller_modify_fme
    NEW_ATTRIBUTES = _response
    PYTHONSOURCE:
      import fme
      import fmeobjects
      import boto3    #need this for AWS access
      import json     #AWS stuff creates json


      def AWSCall(feature):
          ec2 = boto3.resource(
                  'ec2',
                  region_name=feature.getAttribute('aws.region_name'),
                  aws_access_key_id=feature.getAttribute('AWS_ACCESS_KEY_ID'),
                  aws_secret_access_key=feature.getAttribute('AWS_SECRET_ACCESS_KEY'))
          security_group = ec2.SecurityGroup(feature.getAttribute('GroupId'))
          try:
              response = security_group.authorize_ingress(

                  IpPermissions=[
                      {
                          'FromPort': 25,
                          'IpProtocol': 'tcp',
                          'IpRanges': [
                              {
                                  'CidrIp': '0.0.0.0/0',
                              },
                          ],
                          'ToPort': 25,

                      },
                      {
                          'FromPort': 80,
                          'IpProtocol': 'tcp',
                          'IpRanges': [
                              {
                                  'CidrIp': '0.0.0.0/0',
                              },
                          ],
                          'ToPort': 80,

                      },
                      {
                          'FromPort': 443,
                          'IpProtocol': 'tcp',
                          'IpRanges': [
                              {
                                  'CidrIp': '0.0.0.0/0',
                              },
                          ],
                          'ToPort': 443,

                      },
                      {
                          'FromPort': 3389,
                          'IpProtocol': 'tcp',
                          'IpRanges': [
                              {
                                  'CidrIp': '0.0.0.0/0',
                              },
                          ],
                          'ToPort': 3389,

                      },
      {
                          'FromPort': 5900,
                          'IpProtocol': 'tcp',
                          'IpRanges': [
                              {
                                  'CidrIp': '0.0.0.0/0',
                              },
                          ],
                          'ToPort': 5900,

                      },
                      {
                          'FromPort': 7078,
                          'IpProtocol': 'tcp',
                          'IpRanges': [
                              {
                                  'CidrIp': '0.0.0.0/0',
                              },
                          ],
                          'ToPort': 7078,

                      },
                      {
                          'FromPort': 8888,
                          'IpProtocol': 'tcp',
                          'IpRanges': [
                              {
                                  'CidrIp': '0.0.0.0/0',
                              },
                          ],
                          'ToPort': 8888,

                      },
                      {
                          'FromPort': 8080,
                          'IpProtocol': 'tcp',
                          'IpRanges': [
                              {
                                  'CidrIp': '0.0.0.0/0',
                              },
                          ],
                          'ToPort': 8080,
                      },
                  ],


              )
              feature.setAttribute("_response", json.dumps(response, default=str)) #https://stackoverflow.com/questions/11875770/how-to-overcome-datetime-datetime-not-json-serializable
          except Exception as e:
              feature.setAttribute("_exception", 'error in PythonCaller_modify_fme ' + repr(e))
    PYTHONSYMBOL = AWSCall
    -> AttributeExposer

Bookmark: Create FME Server Virtual Machine security group
PythonCaller_create_fmeserver_security_group
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.create_security_group(
                  Description='FME Server',
                  GroupName=feature.getAttribute('fmeserver.securityGroup'),
                  VpcId=feature.getAttribute('Vpc.VpcId'),
              )
              feature.setAttribute("_response", json.dumps(response, default=str)) #https://stackoverflow.com/questions/11875770/how-to-overcome-datetime-datetime-not-json-serializable
          except Exception as e:
              feature.setAttribute("_exception", 'error in PythonCaller_create_fmeserver_security_group: ' + repr(e))
    PYTHONSYMBOL = AWSCall
    -> JSONFlattener_flexnet_3
    -> AttributeExposer
JSONFlattener_flexnet_3
    ERROR_LIST_ATTR = _json_error
    JSON_DOCUMENT = @Value(_response)
    NEW_ATTRIBUTES = GroupId
    READ_FROM_FILE = NO
    RECURSIVE = Yes
    -> PythonCaller_modify_fmeserver
PythonCaller_modify_fmeserver
    NEW_ATTRIBUTES = _response
    PYTHONSOURCE:
      import fme
      import fmeobjects
      import boto3    #need this for AWS access
      import json     #AWS stuff creates json


      def AWSCall(feature):
          ec2 = boto3.resource(
                  'ec2',
                  region_name=feature.getAttribute('aws.region_name'),
                  aws_access_key_id=feature.getAttribute('AWS_ACCESS_KEY_ID'),
                  aws_secret_access_key=feature.getAttribute('AWS_SECRET_ACCESS_KEY'))
          security_group = ec2.SecurityGroup(feature.getAttribute('GroupId'))
          try:
              response = security_group.authorize_ingress(

                  IpPermissions=[
                      {
                          'FromPort': 80,
                          'IpProtocol': 'tcp',
                          'IpRanges': [
                              {
                                  'CidrIp': '0.0.0.0/0',
                              },
                          ],
                          'ToPort': 80,

                      },

                  ],


              )
              feature.setAttribute("_response", json.dumps(response, default=str)) #https://stackoverflow.com/questions/11875770/how-to-overcome-datetime-datetime-not-json-serializable
          except Exception as e:
              feature.setAttribute("_exception", 'error in PythonCaller_modify_fmeserver: ' + repr(e))
    PYTHONSYMBOL = AWSCall
    -> AttributeExposer

Bookmark: Create Internet Gateway
Note: Create Internet Gateway
PythonCaller_create_internet_gateway
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.create_internet_gateway()
              feature.setAttribute("_response", json.dumps(response, default=str)) #https://stackoverflow.com/questions/11875770/how-to-overcome-datetime-datetime-not-json-serializable
          except Exception as e:
              feature.setAttribute("_exception", 'error in PythonCaller_create_internet_gateway: ' + repr(e))
    PYTHONSYMBOL = AWSCall
    -> JSONFlattener
    -> AttributeExposer
JSONFlattener
    ERROR_LIST_ATTR = _json_error
    JSON_DOCUMENT = @Value(_response)
    NEW_ATTRIBUTES = InternetGateway.InternetGatewayId
    READ_FROM_FILE = NO
    RECURSIVE = Yes
    -> PythonCaller_create_internet_gateway_tags
Note: Tag Internet Gateway
PythonCaller_create_internet_gateway_tags
    NEW_ATTRIBUTES = _response
    PYTHONSOURCE:
      import fme
      import fmeobjects
      import boto3    #need this for AWS access
      import json     #AWS stuff creates json


      def AWSCall(feature):
          ec2 = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = ec2.create_tags(
                  Resources=[
                      feature.getAttribute('InternetGateway.InternetGatewayId'),
                  ],
                  Tags=[
                      {
                      'Key': 'Name',
                      'Value': feature.getAttribute('aws.name_tag')
                      },
                  ]
              )
              feature.setAttribute("_response", json.dumps(response, default=str)) #https://stackoverflow.com/questions/11875770/how-to-overcome-datetime-datetime-not-json-serializable
          except Exception as e:
              feature.setAttribute("_exception", 'error in PythonCaller_create_internet_gateway_tags: ' + repr(e))
    PYTHONSYMBOL = AWSCall
    -> PythonCaller_attach_to_vpc
    -> AttributeExposer
Note: Attach Internet Gateway to VPC
PythonCaller_attach_to_vpc
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.attach_internet_gateway(
                  InternetGatewayId=feature.getAttribute('InternetGateway.InternetGatewayId'),
                  VpcId=feature.getAttribute('Vpc.VpcId')
              )
              feature.setAttribute("_response", json.dumps(response, default=str)) #https://stackoverflow.com/questions/11875770/how-to-overcome-datetime-datetime-not-json-serializable
          except Exception as e:
              feature.setAttribute("_exception", 'error in PythonCaller_attach_to_vpc: ' + repr(e))
    PYTHONSYMBOL = AWSCall
    -> PythonCaller_create_route_2
    -> AttributeExposer

Bookmark: Create exit route in Route Table
Note: Find my route table
PythonCaller_create_route_2
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.describe_route_tables(
                  Filters=[
                      {
                          'Name': 'vpc-id',
                          'Values': [
                              feature.getAttribute('Vpc.VpcId'),
                          ]
                      },
                  ],

              )
              feature.setAttribute("_response", json.dumps(response, default=str)) #https://stackoverflow.com/questions/11875770/how-to-overcome-datetime-datetime-not-json-serializable
          except Exception as e:
              feature.setAttribute("_exception", 'error in PythonCaller_create_route_2: ' + repr(e))
    PYTHONSYMBOL = AWSCall
    -> JSONFlattener_route_table
    -> AttributeExposer
JSONFlattener_route_table
    ERROR_LIST_ATTR = _json_error
    JSON_DOCUMENT = @Value(_response)
    READ_FROM_FILE = NO
    RECURSIVE = Yes
    -> AttributeRenamer
AttributeRenamer
    ATTR_TABLE = RENAME_SET_DEFAULT RouteTables{0}.Associations{0}.RouteTableId > RouteTableId
    -> PythonCaller_create_route
PythonCaller_create_route
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.create_route(
                  DestinationCidrBlock='0.0.0.0/0',
                  GatewayId=feature.getAttribute('InternetGateway.InternetGatewayId'),
                  RouteTableId=feature.getAttribute('RouteTableId'),
              )
              feature.setAttribute("_response", json.dumps(response, default=str)) #https://stackoverflow.com/questions/11875770/how-to-overcome-datetime-datetime-not-json-serializable
          except Exception as e:
              feature.setAttribute("_exception", 'error in PythonCaller_create_route: ' + repr(e))
    PYTHONSYMBOL = AWSCall
    -> AttributeExposer

Bookmark: Create Subnets
Junction
    -> ListExploder_subnet_cidr
    -> PythonCaller_describe_availability_zones
Note: Create feature for each subnet cidr
ListExploder_subnet_cidr
    ATTR_ACCUM_MODE = Merge List Attributes
    ATTR_CONFLICT_RES = Use List Attribute Values
    INDEX_ATTR = _element_index
    LIST_ATTR = aws.subnet_cidr{}
    ELEMENTS -> Counter_cidr
Note: count how many cidr we have
Counter_cidr
    CNT_ATTR = _count
    DOMAIN = cidr
    SCOPE = Global
    START = 0
    -> FeatureJoiner [LEFT]
Note: find all availabity zones for selected region
PythonCaller_describe_availability_zones
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.describe_availability_zones()
              feature.setAttribute("_response", json.dumps(response, default=str)) #https://stackoverflow.com/questions/11875770/how-to-overcome-datetime-datetime-not-json-serializable
          except Exception as e:
              feature.setAttribute("_exception", 'error in PythonCaller_describe_availability_zones: ' + repr(e))
    PYTHONSYMBOL = AWSCall
    -> JSONFlattener_availability_zones
    -> AttributeExposer
JSONFlattener_availability_zones
    ERROR_LIST_ATTR = _json_error
    JSON_DOCUMENT = @Value(_response)
    NEW_ATTRIBUTES = AvailabilityZones{} ZoneName State
    READ_FROM_FILE = NO
    RECURSIVE = Yes
    -> ListExploder
Note: Create a feature for each zone
ListExploder
    ATTR_ACCUM_MODE = Merge List Attributes
    ATTR_CONFLICT_RES = Use List Attribute Values
    INDEX_ATTR = _element_index
    LIST_ATTR = AvailabilityZones{}
    ELEMENTS -> Tester_zone_available
Note: Filter out unhealthy zones
Tester_zone_available
    BOOL_OP = OR
    TEST_CLAUSE = TEST @Value(State) = available
    TEST_MODE = TEST
    PASSED -> Counter_ZoneName
Note: Count the zones
Counter_ZoneName
    CNT_ATTR = _count
    DOMAIN = zonename
    SCOPE = Global
    START = 0
    -> FeatureJoiner [RIGHT]
Note: merge cidr options with Zone options
FeatureJoiner
    ATTR_CONFLICT_RES = Use Left
    GEOMETRY_HANDLING = Use Left
    JOIN_KEYS = _count _count AUTO
    JOIN_MODE = Inner
    JOINED -> PythonCaller_create_subnets
Note: Create a subnet for each cidr range
PythonCaller_create_subnets
    NEW_ATTRIBUTES = _response _exception
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.create_subnet(
                  AvailabilityZone=feature.getAttribute('ZoneName'),
                  CidrBlock=feature.getAttribute('aws.subnet_cidr'),
                  VpcId=feature.getAttribute('Vpc.VpcId'),
              )
              feature.setAttribute("_response", json.dumps(response, default=str)) #https://stackoverflow.com/questions/11875770/how-to-overcome-datetime-datetime-not-json-serializable
          except Exception as e:
              feature.setAttribute("_exception", 'error in PythonCaller_create_subnets: ' + repr(e))
    PYTHONSYMBOL = AWSCall
    -> Tester_Create_Subnets_success
Note: Sometimes PythonCaller_describe_availability_zones lies. Catch that lie here. If the Availability Zone doesn't actually exist, filter it out by checking for a value in _exception
Tester_Create_Subnets_success
    BOOL_OP = OR
    COMPOSITE_TEST = 1
    TEST_CLAUSE = TEST _exception NOT_ATTRIBUTE_HAS_A_VALUE ""
    TEST_MODE = TEST
    PASSED -> JSONFlattener_subnets
    FAILED -> Tester_Create_Subnets_success_Failed
JSONFlattener_subnets
    ERROR_LIST_ATTR = _json_error
    JSON_DOCUMENT = @Value(_response)
    NEW_ATTRIBUTES = Subnet.AvailabilityZone Subnet.SubnetId
    READ_FROM_FILE = NO
    RECURSIVE = Yes
    -> AttributeCreator_SubnetTag
AttributeCreator_SubnetTag
    ATTR_TABLE = SET_TO SubnetTag = @Value(aws.name_tag) @Value(ZoneName)
    -> PythonCaller_create_subnet_tags
PythonCaller_create_subnet_tags
    NEW_ATTRIBUTES = _response
    PYTHONSOURCE:
      import fme
      import fmeobjects
      import boto3    #need this for AWS access
      import json     #AWS stuff creates json


      def AWSCall(feature):
          ec2 = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = ec2.create_tags(
                  Resources=[
                      feature.getAttribute('Subnet.SubnetId'),
                  ],
                  Tags=[
                      {
                      'Key': 'Name',
                      'Value': feature.getAttribute('SubnetTag')
                      },
                  ]
              )
              feature.setAttribute("_response", json.dumps(response, default=str)) #https://stackoverflow.com/questions/11875770/how-to-overcome-datetime-datetime-not-json-serializable
          except Exception as e:
              feature.setAttribute("_exception", 'error in PythonCaller_create_subnet_tags: ' + repr(e))
    PYTHONSYMBOL = AWSCall
    -> PythonCaller_enable_public_ip_addresses
    -> AttributeExposer
PythonCaller_enable_public_ip_addresses
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.modify_subnet_attribute(
                  MapPublicIpOnLaunch={
                      'Value': True
                  },
                  SubnetId=feature.getAttribute('Subnet.SubnetId')
              )
              feature.setAttribute("_response", json.dumps(response, default=str)) #https://stackoverflow.com/questions/11875770/how-to-overcome-datetime-datetime-not-json-serializable
          except Exception as e:
              feature.setAttribute("_exception", 'error in PythonCaller_enable_public_ip_addresses: ' + repr(e))
    PYTHONSYMBOL = AWSCall
    -> AttributeExposer
Tester_Create_Subnets_success_Failed: Logger
    LOG_FEATURE = LOG_ONLY
    MAXCOORDS = 20
    MAXFEATS = 20
    MESSAGE = Feature is:
    SEVERITY = INFO

Bookmark: Error in PythonCaller
AttributeExposer
    ATTR_LIST = _exception
    -> Tester_has_exception
Tester_has_exception
    BOOL_OP = OR
    TEST_CLAUSE = TEST _exception ATTRIBUTE_HAS_A_VALUE ""
    TEST_MODE = TEST
    PASSED -> Terminator_exception
Terminator_exception
    MESSAGE = Translation Terminated. @Value(_exception)
