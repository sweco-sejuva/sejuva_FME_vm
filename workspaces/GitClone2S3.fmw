FME workspace GitClone2S3.fmw
Title: FMEDataGit2S3
Description: Mirror the FMEData GitHub repository onto S3. Specify which branch to mirror.
This workspace is run via a GitHub webhook.
https://bluesky-safe-software.fmecloud.com/fmerest/v3/transformations/submit/FMETraining/FMEDataGit2S3.fmw?fmetoken=0da8284a549462da314f97b336723e23178655d5&Branch=2018 
Before publishing:
    Set GITUSER to be your GitHub username 
    Set the GITREPOSITORY to be the GitHub repository 
    Configure the Web Connection used by the S3Uploader

Parameters:
- GITBRANCH = development   # Git Branch
- GITUSER = safesoftware   # GIT user
- GITREPOSITORY = virtualmachines   # GIT Repository
- FME_SHAREDRESOURCE_TEMP = /Users/rcragg/Downloads   # FME Server Temporary Resource Directory

Bookmark: Clone FMEData GitHub repository
Creator
    GEOMTYPE = Geometry Object
    NUM = 1
    CREATED -> AWSCredentialSupplier
AWSCredentialSupplier
    AWS_ACCESS_KEY_ID = AKIAICERN4WDSWP5VUDQ
    AWS_SECRET_ACCESS_KEY =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
    -> FeatureReader [INITIATOR]
Note: The branch will be the CourseType. Make sure they are the same when forking the repository
FeatureReader
    ATTRIBUTES = JSONFeature,"git.username,git.repository,git.branch,aws.name_tag,aws.s3_bucket_name,aws.region_name,aws.vpc_cidr,aws.subnet_cidr{},ami.linux,ami.windows,flexnet.ec2type,flexnet.ec2size,flexnet.volumeSize,flexnet.securityGroup,fmeserver.ec2type,fmeserver.ec2size,fmeserver.volumeSize,fmeserver.securityGroup,fmeserver.docker-compose.yaml,fme.ec2type,fme.ec2size,fme.volumeSize,fme.securityGroup,fme.timezone,fme.portForwarding,fme.firewall,fme.password,fme.license,fme.installApps,fme.vm.instanceInitiatedShutdownBehavior,fme.vm.fromEmail,fme.vm.CCEmail,fme.vm.BCCEmail,web.repository,web.workspace,web.server,web.token,git.aws.files{},fme.vm.template.email{},fme.vm.template.rdp{},fme_geometry{0}"
    ATTR_ACCUM_MODE = Merge Initiator and Result
    ATTR_CONFLICT_RES = Use Result
    COMBINE_GEOM = Use Result
    DATASET = https://raw.githubusercontent.com/$(GITUSER)/$(GITREPOSITORY)/$(GITBRANCH)/settings.json
    FORMAT = JSON
    JSON_DECODE_TEXT_STRINGS = Yes
    JSON_FEATURE_TYPE_KEY = json_featuretype
    JSON_FLATTEN_MODE = ALL_LEVELS
    JSON_GEOMETRY_FORMAT = None
    JSON_SAVE_FRAGMENTS = NO
    JSON_SCAN_MODE = AUTO
    JSON_USE_BASENAME_AS_DEFAULT_FEATURE_TYPE = No
    JSON_USE_SEARCH_ENVELOPE = NO
    OUTPUT_FEATURES_DISPLAY = Schema and Data Features
    JSONFeature -> AttributeKeeper
AttributeKeeper
    KEEP_ATTRS = git.username,AWS_SECRET_ACCESS_KEY,git.branch,aws.s3_bucket_name,aws.vpc_cidr,aws.name_tag,aws.region_name,web.server,web.token,AWS_ACCESS_KEY_ID,web.workspace,git.repository,web.repository
    KEEP_LIST = git.aws.files{}
    -> AttributeManager
Note: AttributeManager [AttributeManager] / Attribute Actions: Input AttributeOutput AttributeAttribute ValueAction<not set>GITUSER$(GITUSER)Set Value<not set>GITREPOSITORY$(GITREPOSITORY)Set Value<not set>GITBRANCH$(GITBRANCH)Set Value<not set>_s3_object_key$(GITBRANCH)Set Value
AttributeManager
    ATTR_TABLE:
      SET_TO GITUSER = $(GITUSER)
      SET_TO GITREPOSITORY = $(GITREPOSITORY)
      SET_TO GITBRANCH = $(GITBRANCH)
      SET_TO _s3_object_key = $(GITBRANCH)
    -> ListExploder
    -> AttributeCreator
AttributeCreator
    ATTR_TABLE:
      SET_TO _response_body = // This JS file is created byGitClone2S3.fmw
        // It takes the contents of settings.json

        var repository, workspace, form, server, token, branch;
        repository = "@Value(web.repository)";
        workspace = "@Value(web.workspace)";
        server  = "@Value(web.server)";
        token =  "@Value(web.token)";
        branch = "@Value(git.branch)";

      SET_TO git.aws.files = js/settings.js
    -> S3Uploader
ListExploder
    ATTR_ACCUM_MODE = Merge List Attributes
    ATTR_CONFLICT_RES = Use List Attribute Values
    INDEX_ATTR = _element_index
    LIST_ATTR = git.aws.files{}
    ELEMENTS -> HTTPCaller
HTTPCaller
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = fme-system
    TARGET_URL = https://raw.githubusercontent.com/@Value(git.username)/@Value(git.repository)/@Value(git.branch)/@Value(git.aws.files)
    TRANSFER_TIMEOUT_LENGTH = 90
    USE_COOKIES = No
    VERIFY_SSL_CERTIFICATES = Yes
    -> S3Uploader

Bookmark: Upload updated folders and the zip file to S3
S3Uploader
    AWS_ACCESS_KEY = @Value(AWS_ACCESS_KEY_ID)
    AWS_SECRET_KEY = @Value(AWS_SECRET_ACCESS_KEY)
    S3_ACCELERATION = No
    S3_AWS_REGION = US East, N. Virginia (us-east-1)
    S3_BUCKET_NAME = @Value(aws.s3_bucket_name)
    S3_CANNED_ACL = Public Read
    S3_CUSTOM_HEADERS = Content-Type;text/html
    S3_DATA = @Value(_response_body)
    S3_FILE_OR_DATA = Attribute or Expression
    S3_OBJECT_KEY = @Value(git.branch)/@Value(git.aws.files)
    S3_UPLOAD_ENCRYPTION = None
    S3_URI_ATTRIBUTE = _s3_object_uri
    -> Logger_S3Output
    <REJECTED> -> Logger_S3Uploader_Rejected
Logger_S3Output
    LOG_FEATURE = LOG_ONLY
    MAXCOORDS = 20
    MAXFEATS = 20
    MESSAGE = Feature is:
    SEVERITY = INFO
Logger_S3Uploader_Rejected
    LOG_FEATURE = LOG_ONLY
    MAXCOORDS = 20
    MAXFEATS = 20
    MESSAGE = Feature is:
    SEVERITY = WARN

Bookmark: Documentation
Note: Created by Ryan Cragg. ryan.cragg@safe.com / Mirror the FMEData GitHub repository onto S3. Specify which branch to mirror. / This workspace is run via a GitHub webhook such as: / https://bluesky-safe-software.fmecloud.com/fmerest/v3/transformations/submit/FMETraining/FMEDataGit2S3.fmw?fmetoken=0da8284a549462da314f97b336723e23178655d5&Branch=2018 / Before publishing: / Set GITUSER to be your GitHub username / Set the GITREPOSITORY to be the GitHub repository / Configure the Web Connection used by the S3Uploader
