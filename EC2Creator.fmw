FME workspace EC2Creator.fmw

Parameters:
- InstanceName = Steve nOT 4   # " " Instance Name
- amiId = ami-e7e78d87   # AMI ID
- SubnetId = subnet-671d923e

Writers:
- TEXTLINE_1: TEXTLINE to C:\apps\FMEServer\Utilities\tomcat\webapps\examples\RDPFiles.zip\FMETraining.rdp
- TEXTLINE_2: TEXTLINE to C:\apps\FMEServer\Utilities\tomcat\webapps\examples\RDPFiles.zip\FMETrainingPort8080.rdp
- TEXTLINE_3: TEXTLINE to C:\apps\FMEServer\Utilities\tomcat\webapps\examples\RDPFiles.zip\FMETrainingPort443.rdp
- TEXTLINE_4: TEXTLINE to C:\apps\FMEServer\Utilities\tomcat\webapps\examples\RDPFiles.zip\readme.txt

Creator
    GEOMTYPE = Geometry Object
    NUM = 1
    CREATED -> UUIDGenerator
UUIDGenerator
    UUID_ATTR = _uuid
    -> AttributeManager
Note: Create contents of .js files and batch files.
AttributeManager
    ATTR_TABLE:
      SET_TO ec2js = var AWS = require('aws-sdk');
        AWS.config.region = 'us-east-1';
        var ec2 = new AWS.EC2();

        var params = {
          ImageId: '$(amiId)', //
          InstanceType: 't2.large',
          MinCount: 1, MaxCount: 1,
          SubnetId: '$(SubnetId)'
         };

        // Create the instance
        ec2.runInstances(params, function(err, data) {
          if (err) { console.log("Could not create instance", err); return; }
          var instanceId = data.Instances[0].InstanceId;

          // Add tags to the instance
          params = {Resources: [instanceId], Tags: [
            {Key: 'Name', Value: '$(InstanceName)'}
          ]};
          ec2.createTags(params, function(err) {
         //   console.log("Tagging instance", err ? "failure" : "success");
          });

          // Find IP address
        	params = {InstanceIds: [instanceId]
        	};

        	ec2.waitFor('instanceRunning', params, function(err, data) {
        		if (err) {console.log("Problem waiting to run", err); return; }// an error occurred
        		console.log(data.Reservations[0].Instances[0].PublicIpAddress);
        	});
        });
      SET_TO launch = @echo off
        call :launch > c:\temp\@Value(_uuid)\launch.log
        goto:eof

        :launch
            node c:\temp\@Value(_uuid)\ec2.js
        goto:eof
    -> AttributeFileWriter
Note: Create .js file
AttributeFileWriter
    FILE_NAME = c:\temp\@Value(_uuid)\EC2.js
    SOURCE_ATTR = ec2js
    CHAR_ENCODING = fme-system
    OVERWRITE_FILE = Overwrite file
    -> AttributeFileWriter_2
Note: Create .bat file
AttributeFileWriter_2
    FILE_NAME = c:\temp\@Value(_uuid)\launch.bat
    SOURCE_ATTR = launch
    CHAR_ENCODING = fme-system
    OVERWRITE_FILE = Overwrite file
    -> AttributeKeeper
AttributeKeeper
    KEEP_ATTRS = _uuid
    -> SystemCaller
Note: Run .bat file.
SystemCaller
    ATTR = exitCode
    CMD = c:\temp\@Value(_uuid)\launch.bat
    -> AttributeFileReader
AttributeFileReader
    FILE_NAME = c:\temp\@Value(_uuid)\launch.log
    CHAR_ENCODING = windows-1252
    DEST_ATTR = PublicIPAddress
    -> AttributeCreator_2
    -> Logger
Logger
    MAXFEATS = 20
    MESSAGE = Feature is:
    MAXCOORDS = 20
    LOGGED -> Cloner
Cloner
    COPYATT = _creation_instance
    COPIES = 3
    COPY -> AttributeCreator_5
Note: set the port numbers and output file names
AttributeCreator_5
    ATTR_LIST = PORT,"FME_CONDITIONAL:DEFAULT_VALUE'_FME_NO_OP_'BOOL_OP;OR;COMPOSITE_TEST;<Unused>;TEST @Value(_creation_instance) = 0'3389'BOOL_OP;OR;COMPOSITE_TEST;<Unused>;TEST @Value(_creation_instance) = 1'8080'BOOL_OP;OR;COMPOSITE_TEST;<Unused>;TEST @Value(_creation_instance) = 2'443'FME_NUM_CONDITIONS4___",FileName,"FME_CONDITIONAL:DEFAULT_VALUE'_FME_NO_OP_'BOOL_OP;OR;COMPOSITE_TEST;<Unused>;TEST @Value(_creation_instance) = 0'FMETraining'BOOL_OP;OR;COMPOSITE_TEST;<Unused>;TEST @Value(_creation_instance) = 1'FMETrainingPort8080'BOOL_OP;OR;COMPOSITE_TEST;<Unused>;TEST @Value(_creation_instance) = 2'FMETrainingPort443'FME_NUM_CONDITIONS4___"
    -> AttributeCreator
Note: set the contents of the RDP file / Some useful info here: / http://chall32.blogspot.ca/2012/04/fixing-remote-desktop-annoyances.html
AttributeCreator
    ATTR_LIST:
      text_line_data,full address:s:@Value(PublicIPAddress):@Value(PORT)
      username:s:Administrator
      domain:s:FMETraining
      screen mode id:i:2
      use multimon:i:0
      session bpp:i:24
      compression:i:1
      keyboardhook:i:1
      audiocapturemode:i:0
      videoplaybackmode:i:1
      connection type:i:2
      displayconnectionbar:i:1
      disable wallpaper:i:1
      allow font smoothing:i:0
      allow desktop composition:i:0
      disable full window drag:i:1
      disable menu anims:i:1
      disable themes:i:1
      disable cursor setting:i:0
      bitmapcachepersistenable:i:0
      audiomode:i:0
      redirectprinters:i:0
      redirectcomports:i:0
      redirectsmartcards:i:1
      redirectclipboard:i:0
      redirectposdevices:i:0
      redirectdirectx:i:1
      autoreconnection enabled:i:1
      authentication level:i:0
      prompt for credentials:i:0
      negotiate security layer:i:1
      remoteapplicationmode:i:0
      alternate shell:s:
      shell working directory:s:
      gatewayhostname:s:
      gatewayusagemethod:i:4
      gatewaycredentialssource:i:4
      gatewayprofileusagemethod:i:0
      promptcredentialonce:i:1
      use redirection server name:i:0
      enablecredsspsupport:i:0
      drivestoredirect:s:
    -> AttributeFilter
AttributeFilter
    ATTR_NAME = PORT
    ATTR_VALUES = <EMPTY>,<MISSING>,<NULL>,<UNFILTERED>,3389,8080,443
    3389 -> text_line (writer TEXTLINE_1)
    8080 -> text_line (writer TEXTLINE_2)
    443 -> text_line (writer TEXTLINE_3)
text_line (writer TEXTLINE_1)
    attributes: text_line_data buffer
text_line (writer TEXTLINE_2)
    attributes: text_line_data buffer
text_line (writer TEXTLINE_3)
    attributes: text_line_data buffer
Note: Create the readme file text
AttributeCreator_2
    ATTR_LIST:
      text_line_data,These RDP files can be used to connect to your training machine for the FME Online Training.

      The password is:
      feature manipulation engine

      Please try FMETraining.rdp first.

      Some organizations block the port used by RDP; port 3389.

      If FMETraining.rdp does not work, please try the other two RDP files; FMETrainingPort8080.rdp and FMETrainingPort443.rdp.
      These RDP files use different ports that might not be blocked.

      If ports 443 and 8080 also do not work, then your Security Administrator is likely using a Web Security Gateway. This cannot be bypassed without contacting your IT Department.
      Please contact your IT Department for further assistance. Tell them that you need to use Remote Desktop to connect to @Value(PublicIPAddress).
    -> text_line (writer TEXTLINE_4)
Note: readme.txt
text_line (writer TEXTLINE_4)
    attributes: text_line_data buffer
